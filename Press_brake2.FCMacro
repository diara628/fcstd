# Macro Begin: /home/drayko/FreeCAD/fcstd/Press_brake2.FCMacro +++++++++++++++++++++++++++++++++++++++++++++++++
import FreeCAD
import Draft

#Gui.activateWorkbench("DraftWorkbench")
#Gui.activeDocument().activeView().viewBottom()
#Gui.activeDocument().activeView().viewBottom()
Draft.makeDimension(FreeCAD.Vector(-250.0,100.0,0.0),FreeCAD.Vector(-250.0,-100.0,0.0),FreeCAD.Vector(-329.0,-60.0,0.0))
App.getDocument("Simple_modular_press_brake").removeObject("Shape2DView002")
App.getDocument("Simple_modular_press_brake").removeObject("Shape2DView001")
Draft.makeDimension(FreeCAD.Vector(-250.0,-100.0,0.0),FreeCAD.Vector(250.0,-100.0,0.0),FreeCAD.Vector(250.0,-168.0,0.0))
FreeCAD.getDocument("Simple_modular_press_brake").getObject("Dimension").Label = "W"
FreeCAD.getDocument("Simple_modular_press_brake").getObject("Dimension").Label = "Wi"
FreeCAD.getDocument("Simple_modular_press_brake").getObject("Dimension").Label = "Wid"
FreeCAD.getDocument("Simple_modular_press_brake").getObject("Dimension").Label = "Widt"
FreeCAD.getDocument("Simple_modular_press_brake").getObject("Dimension").Label = "Width"
FreeCAD.getDocument("Simple_modular_press_brake").getObject("Shape2DView").ProjectionMode = "Individual Faces"
FreeCAD.getDocument("Simple_modular_press_brake").getObject("Shape2DView").ProjectionMode = "Cutlines"
FreeCAD.getDocument("Simple_modular_press_brake").getObject("Shape2DView").Projection = (0.00, 0.00, 0.00)
FreeCAD.getDocument("Simple_modular_press_brake").getObject("Shape2DView").Projection = (0.00, 1.00, 0.00)
FreeCAD.getDocument("Simple_modular_press_brake").getObject("Shape2DView").Placement = App.Placement(App.Vector(0,5,0),App.Rotation(0,0,0,1))
FreeCAD.getDocument("Simple_modular_press_brake").getObject("Shape2DView").Placement = App.Placement(App.Vector(0,50,0),App.Rotation(0,0,0,1))
FreeCAD.getDocument("Simple_modular_press_brake").getObject("Shape2DView").Placement = App.Placement(App.Vector(0,500,0),App.Rotation(0,0,0,1))
FreeCAD.getDocument("Simple_modular_press_brake").getObject("Shape2DView").Placement = App.Placement(App.Vector(0,50,0),App.Rotation(0,0,0,1))
FreeCAD.getDocument("Simple_modular_press_brake").getObject("Shape2DView").Placement = App.Placement(App.Vector(0,5,0),App.Rotation(0,0,0,1))
FreeCAD.getDocument("Simple_modular_press_brake").getObject("Shape2DView").Placement = App.Placement(App.Vector(0,0,0),App.Rotation(0,0,0,1))
FreeCAD.getDocument("Simple_modular_press_brake").getObject("Shape2DView").Placement = App.Placement(App.Vector(0,0,5),App.Rotation(0,0,0,1))
FreeCAD.getDocument("Simple_modular_press_brake").getObject("Shape2DView").Placement = App.Placement(App.Vector(0,0,50),App.Rotation(0,0,0,1))
FreeCAD.getDocument("Simple_modular_press_brake").getObject("Shape2DView").Placement = App.Placement(App.Vector(0,0,500),App.Rotation(0,0,0,1))
FreeCAD.getDocument("Simple_modular_press_brake").getObject("Shape2DView").Placement = App.Placement(App.Vector(0,0,5000),App.Rotation(0,0,0,1))
FreeCAD.getDocument("Simple_modular_press_brake").getObject("Shape2DView").Placement = App.Placement(App.Vector(0,0,500),App.Rotation(0,0,0,1))
#Gui.activeDocument().activeView().viewFront()
#Gui.activeDocument().activeView().viewTop()
FreeCAD.getDocument("Simple_modular_press_brake").getObject("ViewShape2DView").Direction = (0.00, 0.00, 1.00)
FreeCAD.getDocument("Simple_modular_press_brake").getObject("ViewShape2DView").Scale = 1.00
FreeCAD.getDocument("Simple_modular_press_brake").getObject("ViewShape2DView").Scale = 0.00
FreeCAD.getDocument("Simple_modular_press_brake").getObject("ViewShape2DView").Scale = 0.20
FreeCAD.getDocument("Simple_modular_press_brake").getObject("ViewShape2DView").Scale = 0.00
FreeCAD.getDocument("Simple_modular_press_brake").getObject("ViewShape2DView").Scale = 0.40
FreeCAD.getDocument("Simple_modular_press_brake").getObject("ViewDimension").Scale = 0.00
FreeCAD.getDocument("Simple_modular_press_brake").getObject("ViewDimension").Scale = 0.40
FreeCAD.getDocument("Simple_modular_press_brake").getObject("ViewDimension001").Scale = 2.00
FreeCAD.getDocument("Simple_modular_press_brake").getObject("ViewDimension001").Scale = 0.00
FreeCAD.getDocument("Simple_modular_press_brake").getObject("ViewDimension001").Scale = 0.40
FreeCAD.getDocument("Simple_modular_press_brake").getObject("ViewDimension001").Scale = 0.00
FreeCAD.getDocument("Simple_modular_press_brake").getObject("ViewDimension").Scale = 0.00
FreeCAD.getDocument("Simple_modular_press_brake").getObject("ViewShape2DView").Scale = 0.00
FreeCAD.getDocument("Simple_modular_press_brake").getObject("ViewDimension001").Scale = 0.20
FreeCAD.getDocument("Simple_modular_press_brake").getObject("ViewDimension").Scale = 0.20
FreeCAD.getDocument("Simple_modular_press_brake").getObject("ViewShape2DView").Scale = 0.20
FreeCAD.getDocument("Simple_modular_press_brake").getObject("ViewDimension001").X = 1.00
FreeCAD.getDocument("Simple_modular_press_brake").getObject("ViewDimension").X = 1.00
FreeCAD.getDocument("Simple_modular_press_brake").getObject("ViewShape2DView").X = 1.00
FreeCAD.getDocument("Simple_modular_press_brake").getObject("ViewDimension001").X = 10.00
FreeCAD.getDocument("Simple_modular_press_brake").getObject("ViewDimension").X = 10.00
FreeCAD.getDocument("Simple_modular_press_brake").getObject("ViewShape2DView").X = 10.00
FreeCAD.getDocument("Simple_modular_press_brake").getObject("ViewDimension001").X = 100.00
FreeCAD.getDocument("Simple_modular_press_brake").getObject("ViewDimension").X = 100.00
FreeCAD.getDocument("Simple_modular_press_brake").getObject("ViewShape2DView").X = 100.00
FreeCAD.getDocument("Simple_modular_press_brake").getObject("ViewDimension001").Y = 5.00
FreeCAD.getDocument("Simple_modular_press_brake").getObject("ViewDimension").Y = 5.00
FreeCAD.getDocument("Simple_modular_press_brake").getObject("ViewShape2DView").Y = 5.00
FreeCAD.getDocument("Simple_modular_press_brake").getObject("ViewDimension001").Y = 50.00
FreeCAD.getDocument("Simple_modular_press_brake").getObject("ViewDimension").Y = 50.00
FreeCAD.getDocument("Simple_modular_press_brake").getObject("ViewShape2DView").Y = 50.00
#Gui.activeDocument().activeView().viewFront()
FreeCAD.getDocument("Simple_modular_press_brake").getObject("Shape2DView001").Projection = (0.00, 1.00, 1.00)
FreeCAD.getDocument("Simple_modular_press_brake").getObject("Shape2DView001").Projection = (0.00, 1.00, 0.00)
App.getDocument("Simple_modular_press_brake").removeObject("Shape2DView001")
FreeCAD.getDocument("Simple_modular_press_brake").getObject("Shape2DView001").Projection = (0.00, 1.00, 1.00)
FreeCAD.getDocument("Simple_modular_press_brake").getObject("Shape2DView001").Projection = (0.00, 1.00, 0.00)
#Gui.activeDocument().activeView().viewFront()
FreeCAD.getDocument("Simple_modular_press_brake").getObject("Shape2DView001").Placement = App.Placement(App.Vector(0,1,0),App.Rotation(0,0,0,1))
FreeCAD.getDocument("Simple_modular_press_brake").getObject("Shape2DView001").Placement = App.Placement(App.Vector(0,10,0),App.Rotation(0,0,0,1))
FreeCAD.getDocument("Simple_modular_press_brake").getObject("Shape2DView001").Placement = App.Placement(App.Vector(0,100,0),App.Rotation(0,0,0,1))
FreeCAD.getDocument("Simple_modular_press_brake").getObject("Shape2DView001").Placement = App.Placement(App.Vector(0,0,0),App.Rotation(0,0,0,1))
FreeCAD.getDocument("Simple_modular_press_brake").getObject("Shape2DView001").Placement = App.Placement(App.Vector(0,20,0),App.Rotation(0,0,0,1))
FreeCAD.getDocument("Simple_modular_press_brake").getObject("Shape2DView001").Placement = App.Placement(App.Vector(0,250,0),App.Rotation(0,0,0,1))
FreeCAD.getDocument("Simple_modular_press_brake").getObject("Shape2DView001").ProjectionMode = "Individual Faces"
FreeCAD.getDocument("Simple_modular_press_brake").getObject("Shape2DView001").ProjectionMode = "Cutlines"
App.getDocument("Simple_modular_press_brake").removeObject("Shape2DView001")
#Gui.activeDocument().activeView().viewTop()
#Gui.activeDocument().activeView().viewBottom()
#Gui.activeDocument().activeView().viewRear()
#Gui.activeDocument().activeView().viewLeft()
#Gui.activeDocument().activeView().viewRight()
#Gui.activeDocument().activeView().viewFront()
FreeCAD.getDocument("Simple_modular_press_brake").getObject("Shape2DView001").Projection = (0.00, 1.00, 1.00)
FreeCAD.getDocument("Simple_modular_press_brake").getObject("Shape2DView001").Projection = (0.00, 1.00, 0.00)
FreeCAD.getDocument("Simple_modular_press_brake").getObject("Shape2DView001").Placement = App.Placement(App.Vector(0,0,0),App.Rotation(0,0,0,1))
FreeCAD.getDocument("Simple_modular_press_brake").getObject("Shape2DView001").Placement = App.Placement(App.Vector(0,0,0),App.Rotation(0,0,0,1))
FreeCAD.getDocument("Simple_modular_press_brake").getObject("Shape2DView001").Placement = App.Placement(App.Vector(0,0,0),App.Rotation(0,0,0,1))
FreeCAD.getDocument("Simple_modular_press_brake").getObject("Shape2DView001").Placement = App.Placement(App.Vector(0,0,0),App.Rotation(0,0,0,1))
FreeCAD.getDocument("Simple_modular_press_brake").getObject("Shape2DView001").Placement = App.Placement(App.Vector(0,0,0),App.Rotation(0,0,0,1))
FreeCAD.getDocument("Simple_modular_press_brake").getObject("Shape2DView001").Placement = App.Placement(App.Vector(0,0,0),App.Rotation(0,0.055479,-0.055479,0.996917))
FreeCAD.getDocument("Simple_modular_press_brake").getObject("Shape2DView001").Placement = App.Placement(App.Vector(0,0,0),App.Rotation(0,0.5,-0.5,0.707107))
FreeCAD.getDocument("Simple_modular_press_brake").getObject("Shape2DView001").Placement = App.Placement(App.Vector(0,0,0),App.Rotation(0,0.055479,-0.055479,0.996917))
FreeCAD.getDocument("Simple_modular_press_brake").getObject("Shape2DView001").Placement = App.Placement(App.Vector(0,0,0),App.Rotation(0,0.055479,-0.055479,0.996917))
FreeCAD.getDocument("Simple_modular_press_brake").getObject("Shape2DView001").Placement = App.Placement(App.Vector(0,0,0),App.Rotation(0,0.0784592,0,0.996917))
FreeCAD.getDocument("Simple_modular_press_brake").getObject("Shape2DView001").Placement = App.Placement(App.Vector(0,0,0),App.Rotation(0,0.707107,0,0.707107))
FreeCAD.getDocument("Simple_modular_press_brake").getObject("Shape2DView001").Placement = App.Placement(App.Vector(0,0,0),App.Rotation(0.5,0.5,0,0.707107))
FreeCAD.getDocument("Simple_modular_press_brake").getObject("Shape2DView001").Placement = App.Placement(App.Vector(0,0,0),App.Rotation(0.408248,0.408248,0.408248,0.707107))
FreeCAD.getDocument("Simple_modular_press_brake").getObject("Shape2DView001").Placement = App.Placement(App.Vector(0,0,0),App.Rotation(0,0.5,0.5,0.707107))
FreeCAD.getDocument("Simple_modular_press_brake").getObject("Shape2DView001").Placement = App.Placement(App.Vector(0,0,0),App.Rotation(0,0.707107,0,0.707107))
FreeCAD.getDocument("Simple_modular_press_brake").getObject("Shape2DView001").Placement = App.Placement(App.Vector(0,0,0),App.Rotation(0,0,0,1))
FreeCAD.getDocument("Simple_modular_press_brake").getObject("Shape2DView001").Placement = App.Placement(App.Vector(0,0,0),App.Rotation(0,0,0,1))
FreeCAD.getDocument("Simple_modular_press_brake").getObject("Shape2DView001").Placement = App.Placement(App.Vector(0,0,0),App.Rotation(0,0,0,1))
FreeCAD.getDocument("Simple_modular_press_brake").getObject("Shape2DView001").Placement = App.Placement(App.Vector(0,0,0),App.Rotation(0.0784591,0,0,0.996917))
FreeCAD.getDocument("Simple_modular_press_brake").getObject("Shape2DView001").Placement = App.Placement(App.Vector(0,0,0),App.Rotation(0.707107,0,0,0.707107))
FreeCAD.getDocument("Simple_modular_press_brake").getObject("Shape2DView001").Placement = App.Placement(App.Vector(0,0,0),App.Rotation(0.5,0.5,0,0.707107))
FreeCAD.getDocument("Simple_modular_press_brake").getObject("Shape2DView001").Placement = App.Placement(App.Vector(0,0,0),App.Rotation(0.00617059,0.00617059,0,0.999962))
FreeCAD.getDocument("Simple_modular_press_brake").getObject("Shape2DView001").Placement = App.Placement(App.Vector(0,0,0),App.Rotation(0.110616,0.110616,0,0.987688))
FreeCAD.getDocument("Simple_modular_press_brake").getObject("Shape2DView001").Placement = App.Placement(App.Vector(0,0,0),App.Rotation(0.707107,0.707107,0,6.12303e-17))
FreeCAD.getDocument("Simple_modular_press_brake").getObject("Shape2DView001").Placement = App.Placement(App.Vector(0,0,0),App.Rotation(0.110616,0.110616,0,0.987688))
FreeCAD.getDocument("Simple_modular_press_brake").getObject("Shape2DView001").Placement = App.Placement(App.Vector(0,0,0),App.Rotation(0.00617059,0.00617059,0,0.999962))
FreeCAD.getDocument("Simple_modular_press_brake").getObject("Shape2DView001").Placement = App.Placement(App.Vector(0,0,0),App.Rotation(0.0246777,0.0246777,0,0.999391))
FreeCAD.getDocument("Simple_modular_press_brake").getObject("Shape2DView001").Placement = App.Placement(App.Vector(0,0,0),App.Rotation(0.270598,0.270598,0,0.92388))
FreeCAD.getDocument("Simple_modular_press_brake").getObject("Shape2DView001").Placement = App.Placement(App.Vector(0,0,0),App.Rotation(0.0246777,0.0246777,0,0.999391))
FreeCAD.getDocument("Simple_modular_press_brake").getObject("Shape2DView001").Placement = App.Placement(App.Vector(0,0,0),App.Rotation(0.055479,0.055479,0,0.996917))
FreeCAD.getDocument("Simple_modular_press_brake").getObject("Shape2DView001").Placement = App.Placement(App.Vector(0,0,0),App.Rotation(0.5,0.5,0,0.707107))
FreeCAD.getDocument("Simple_modular_press_brake").getObject("Shape2DView001").Placement = App.Placement(App.Vector(0,0,0),App.Rotation(0.5,0.5,0,0.707107))
FreeCAD.getDocument("Simple_modular_press_brake").getObject("Shape2DView001").Placement = App.Placement(App.Vector(0,0,0),App.Rotation(0.5,0.5,0,0.707107))
FreeCAD.getDocument("Simple_modular_press_brake").getObject("Shape2DView001").Placement = App.Placement(App.Vector(0,0,0),App.Rotation(0.5,0.5,0,0.707107))
FreeCAD.getDocument("Simple_modular_press_brake").getObject("Shape2DView001").Placement = App.Placement(App.Vector(0,0,0),App.Rotation(0.408248,0.408248,0.408248,0.707107))
FreeCAD.getDocument("Simple_modular_press_brake").getObject("Shape2DView001").Placement = App.Placement(App.Vector(0,0,0),App.Rotation(0.5,0.5,0,0.707107))
FreeCAD.getDocument("Simple_modular_press_brake").getObject("Shape2DView001").Placement = App.Placement(App.Vector(0,0,0),App.Rotation(0.00617059,0.00617059,0,0.999962))
FreeCAD.getDocument("Simple_modular_press_brake").getObject("Shape2DView001").Placement = App.Placement(App.Vector(0,0,0),App.Rotation(0.0800468,0.0800468,0,0.993572))
FreeCAD.getDocument("Simple_modular_press_brake").getObject("Shape2DView001").Placement = App.Placement(App.Vector(0,0,0),App.Rotation(0.653281,0.653281,0,0.382683))
FreeCAD.getDocument("Simple_modular_press_brake").getObject("Shape2DView001").Placement = App.Placement(App.Vector(0,0,0),App.Rotation(0.0800468,0.0800468,0,0.993572))
FreeCAD.getDocument("Simple_modular_press_brake").getObject("Shape2DView001").Placement = App.Placement(App.Vector(0,0,0),App.Rotation(0.00617059,0.00617059,0,0.999962))
FreeCAD.getDocument("Simple_modular_press_brake").getObject("Shape2DView001").Placement = App.Placement(App.Vector(0,0,0),App.Rotation(0.0739128,0.0739128,0,0.994522))
FreeCAD.getDocument("Simple_modular_press_brake").getObject("Shape2DView001").Placement = App.Placement(App.Vector(0,0,0),App.Rotation(0.612372,0.612372,0,0.5))
FreeCAD.getDocument("Simple_modular_press_brake").getObject("Shape2DView001").Placement = App.Placement(App.Vector(0,0,0),App.Rotation(0.0739128,0.0739128,0,0.994522))
FreeCAD.getDocument("Simple_modular_press_brake").getObject("Shape2DView001").Placement = App.Placement(App.Vector(0,0,0),App.Rotation(0.00617059,0.00617059,0,0.999962))
FreeCAD.getDocument("Simple_modular_press_brake").getObject("Shape2DView001").Placement = App.Placement(App.Vector(0,0,0),App.Rotation(0.0616284,0.0616284,0,0.996195))
FreeCAD.getDocument("Simple_modular_press_brake").getObject("Shape2DView001").Placement = App.Placement(App.Vector(0,0,0),App.Rotation(0.541675,0.541675,0,0.642788))
FreeCAD.getDocument("Simple_modular_press_brake").getObject("Shape2DView001").Placement = App.Placement(App.Vector(0,0,0),App.Rotation(0.0616284,0.0616284,0,0.996195))
FreeCAD.getDocument("Simple_modular_press_brake").getObject("Shape2DView001").Placement = App.Placement(App.Vector(0,0,0),App.Rotation(0.00617059,0.00617059,0,0.999962))
FreeCAD.getDocument("Simple_modular_press_brake").getObject("Shape2DView001").Placement = App.Placement(App.Vector(0,0,0),App.Rotation(0.0616284,0.0616284,0,0.996195))
FreeCAD.getDocument("Simple_modular_press_brake").getObject("Shape2DView001").Placement = App.Placement(App.Vector(0,0,0),App.Rotation(0.541675,0.541675,0,0.642788))
FreeCAD.getDocument("Simple_modular_press_brake").getObject("Shape2DView001").Placement = App.Placement(App.Vector(0,0,0),App.Rotation(0.0616284,0.0616284,0,0.996195))
FreeCAD.getDocument("Simple_modular_press_brake").getObject("Shape2DView001").Placement = App.Placement(App.Vector(0,0,0),App.Rotation(0.00617059,0.00617059,0,0.999962))
FreeCAD.getDocument("Simple_modular_press_brake").getObject("Shape2DView001").Placement = App.Placement(App.Vector(0,0,0),App.Rotation(0.0123407,0.0123407,0,0.999848))
FreeCAD.getDocument("Simple_modular_press_brake").getObject("Shape2DView001").Placement = App.Placement(App.Vector(0,0,0),App.Rotation(0.122788,0.122788,0,0.984808))
FreeCAD.getDocument("Simple_modular_press_brake").getObject("Shape2DView001").Placement = App.Placement(App.Vector(0,0,0),App.Rotation(0.696364,0.696364,0,-0.173648))
FreeCAD.getDocument("Simple_modular_press_brake").getObject("Shape2DView001").Placement = App.Placement(App.Vector(0,0,0),App.Rotation(0.122788,0.122788,0,0.984808))
FreeCAD.getDocument("Simple_modular_press_brake").getObject("Shape2DView001").Placement = App.Placement(App.Vector(0,0,0),App.Rotation(0.0123407,0.0123407,0,0.999848))
FreeCAD.getDocument("Simple_modular_press_brake").getObject("Shape2DView001").Placement = App.Placement(App.Vector(0,0,0),App.Rotation(0.165071,0.165071,0,0.97237))
FreeCAD.getDocument("Simple_modular_press_brake").getObject("Shape2DView001").Placement = App.Placement(App.Vector(0,0,0),App.Rotation(0.5,0.5,0,-0.707107))
FreeCAD.getDocument("Simple_modular_press_brake").getObject("Shape2DView001").Placement = App.Placement(App.Vector(0,0,0),App.Rotation(0.165071,0.165071,0,0.97237))
FreeCAD.getDocument("Simple_modular_press_brake").getObject("Shape2DView001").Placement = App.Placement(App.Vector(0,0,0),App.Rotation(0.0123407,0.0123407,0,0.999848))
FreeCAD.getDocument("Simple_modular_press_brake").getObject("Shape2DView001").Placement = App.Placement(App.Vector(0,0,0),App.Rotation(0.12886,0.12886,0,0.983255))
FreeCAD.getDocument("Simple_modular_press_brake").getObject("Shape2DView001").Placement = App.Placement(App.Vector(0,0,0),App.Rotation(0.683013,0.683013,0,-0.258819))
FreeCAD.getDocument("Simple_modular_press_brake").getObject("Shape2DView001").Placement = App.Placement(App.Vector(0,0,0),App.Rotation(0.683013,0.683013,0,-0.258819))
FreeCAD.getDocument("Simple_modular_press_brake").getObject("Shape2DView001").Placement = App.Placement(App.Vector(0,0,0),App.Rotation(0.557678,0.557678,0.557678,-0.258819))
FreeCAD.getDocument("Simple_modular_press_brake").getObject("Shape2DView001").Placement = App.Placement(App.Vector(0,0,0),App.Rotation(0.100256,0.100256,0.100256,0.984808))
FreeCAD.getDocument("Simple_modular_press_brake").getObject("Shape2DView001").Placement = App.Placement(App.Vector(0,0,0),App.Rotation(0.408248,0.408248,0.408248,-0.707107))
FreeCAD.getDocument("Simple_modular_press_brake").getObject("Shape2DView001").Placement = App.Placement(App.Vector(0,0,0),App.Rotation(0.100256,0.100256,0.100256,0.984808))
FreeCAD.getDocument("Simple_modular_press_brake").getObject("Shape2DView001").Placement = App.Placement(App.Vector(0,0,0),App.Rotation(0.442276,0.442276,0.442276,-0.642788))
FreeCAD.getDocument("Simple_modular_press_brake").getObject("Shape2DView001").Placement = App.Placement(App.Vector(0,0,0),App.Rotation(0.100256,0.100256,0.100256,0.984808))
FreeCAD.getDocument("Simple_modular_press_brake").getObject("Shape2DView001").Placement = App.Placement(App.Vector(0,0,0),App.Rotation(0.472938,0.472938,0.472938,-0.573576))
FreeCAD.getDocument("Simple_modular_press_brake").getObject("Shape2DView001").Placement = App.Placement(App.Vector(0,0,0),App.Rotation(0.100256,0.100256,0.100256,0.984808))
FreeCAD.getDocument("Simple_modular_press_brake").getObject("Shape2DView001").Placement = App.Placement(App.Vector(0,0,0),App.Rotation(0.5,0.5,0.5,-0.5))
FreeCAD.getDocument("Simple_modular_press_brake").getObject("Shape2DView001").Placement = App.Placement(App.Vector(0,1,0),App.Rotation(0.5,0.5,0.5,-0.5))
FreeCAD.getDocument("Simple_modular_press_brake").getObject("Shape2DView001").Placement = App.Placement(App.Vector(0,15,0),App.Rotation(0.5,0.5,0.5,-0.5))
FreeCAD.getDocument("Simple_modular_press_brake").getObject("Shape2DView001").Placement = App.Placement(App.Vector(0,150,0),App.Rotation(0.5,0.5,0.5,-0.5))
#Gui.activeDocument().activeView().viewFront()
#Gui.activeDocument().activeView().viewRear()
#Gui.getDocument("Simple_modular_press_brake").getObject("Pad005").Visibility=False
#Gui.activeDocument().activeView().viewFront()
#Gui.getDocument("Simple_modular_press_brake").getObject("Pad005").Visibility=True
#Gui.activeDocument().activeView().viewAxometric()
FreeCAD.getDocument("Simple_modular_press_brake").getObject("Shape2DView001").Placement = App.Placement(App.Vector(0,-150,0),App.Rotation(0.5,0.5,0.5,-0.5))
#Gui.activeDocument().activeView().viewAxometric()
#Gui.SendMsgToActiveView("Save")
App.getDocument("Simple_modular_press_brake").save()
App.ActiveDocument.Sketch.setDatum(15,450.000000)
#Gui.getDocument('Simple_modular_press_brake').resetEdit()
App.getDocument('Simple_modular_press_brake').recompute()
#Gui.activeDocument().activeView().viewTop()
#Gui.activeDocument().activeView().viewFront()
#Gui.SendMsgToActiveView("Save")
App.getDocument("Simple_modular_press_brake").save()

# Macro End: /home/drayko/FreeCAD/fcstd/Press_brake2.FCMacro +++++++++++++++++++++++++++++++++++++++++++++++++
