# Macro Begin: /home/drayko/FreeCAD/fcstd/Press_brake.FCMacro +++++++++++++++++++++++++++++++++++++++++++++++++
import FreeCAD
import Sketcher
import PartDesign
import Drawing

App.activeDocument().addObject('Sketcher::SketchObject','Sketch')
App.activeDocument().Sketch.Placement = App.Placement(App.Vector(0.000000,0.000000,0.000000),App.Rotation(0.000000,0.000000,0.000000,1.000000))
#Gui.activeDocument().activeView().setCamera('#Inventor V2.1 ascii \n OrthographicCamera {\n viewportMapping ADJUST_CAMERA \n position 0 0 87 \n orientation 0 0 1  0 \n nearDistance -112.88701 \n farDistance 287.28702 \n aspectRatio 1 \n focalDistance 87 \n height 143.52005 }')
#Gui.activeDocument().setEdit('Sketch')
App.ActiveDocument.Sketch.addGeometry(Part.Line(App.Vector(-70.104027,29.808012,0),App.Vector(69.441628,29.808012,0)))
App.ActiveDocument.Sketch.addGeometry(Part.Line(App.Vector(69.441628,29.808012,0),App.Vector(69.441628,-30.028812,0)))
App.ActiveDocument.Sketch.addGeometry(Part.Line(App.Vector(69.441628,-30.028812,0),App.Vector(-70.104027,-30.028812,0)))
App.ActiveDocument.Sketch.addGeometry(Part.Line(App.Vector(-70.104027,-30.028812,0),App.Vector(-70.104027,29.808012,0)))
App.ActiveDocument.Sketch.addConstraint(Sketcher.Constraint('Coincident',0,2,1,1)) 
App.ActiveDocument.Sketch.addConstraint(Sketcher.Constraint('Coincident',1,2,2,1)) 
App.ActiveDocument.Sketch.addConstraint(Sketcher.Constraint('Coincident',2,2,3,1)) 
App.ActiveDocument.Sketch.addConstraint(Sketcher.Constraint('Coincident',3,2,0,1)) 
App.ActiveDocument.Sketch.addConstraint(Sketcher.Constraint('Horizontal',0)) 
App.ActiveDocument.Sketch.addConstraint(Sketcher.Constraint('Horizontal',2)) 
App.ActiveDocument.Sketch.addConstraint(Sketcher.Constraint('Vertical',1)) 
App.ActiveDocument.Sketch.addConstraint(Sketcher.Constraint('Vertical',3)) 
#App.ActiveDocument.recompute()
App.ActiveDocument.Sketch.addGeometry(Part.Circle(App.Vector(-49.790424,-0.441598,0),App.Vector(0,0,1),10.079717))
#App.ActiveDocument.recompute()
App.ActiveDocument.Sketch.addGeometry(Part.Circle(App.Vector(50.011230,-0.441598,0),App.Vector(0,0,1),10.187948))
#App.ActiveDocument.recompute()
App.ActiveDocument.Sketch.addConstraint(Sketcher.Constraint('PointOnObject',5,3,-1)) 
App.ActiveDocument.Sketch.addConstraint(Sketcher.Constraint('Equal',5,4)) 
#App.ActiveDocument.recompute()
App.ActiveDocument.Sketch.addConstraint(Sketcher.Constraint('Symmetric',0,2,1,2,-1)) 
#App.ActiveDocument.recompute()
App.ActiveDocument.Sketch.addConstraint(Sketcher.Constraint('Symmetric',0,1,0,2,-2)) 
#App.ActiveDocument.recompute()
App.ActiveDocument.Sketch.addConstraint(Sketcher.Constraint('Symmetric',4,3,5,3,-2)) 
#App.ActiveDocument.recompute()
App.ActiveDocument.Sketch.addConstraint(Sketcher.Constraint('DistanceX',0,1,4,3,19.946635)) 
App.ActiveDocument.Sketch.setDatum(13,50.000000)
App.ActiveDocument.Sketch.movePoint(4,0,App.Vector(-12.475203,-6.403203,0),0)
#App.ActiveDocument.recompute()
App.ActiveDocument.Sketch.addConstraint(Sketcher.Constraint('Radius',4,10.181814)) 
App.ActiveDocument.Sketch.setDatum(14,20.000000)
App.ActiveDocument.Sketch.addConstraint(Sketcher.Constraint('DistanceX',0,1,0,2,140.783071)) 
App.ActiveDocument.Sketch.setDatum(15,500.000000)
App.ActiveDocument.Sketch.addConstraint(Sketcher.Constraint('DistanceY',0,1,2,2,-59.916203)) 
App.ActiveDocument.Sketch.setDatum(16,-200.000000)
#Gui.getDocument('Unnamed').resetEdit()
App.getDocument('Unnamed').recompute()
App.activeDocument().addObject("PartDesign::Pad","Pad")
App.activeDocument().Pad.Sketch = App.activeDocument().Sketch
App.activeDocument().Pad.Length = 10.0
#App.ActiveDocument.recompute()
#Gui.activeDocument().hide("Sketch")
#Gui.activeDocument().setEdit('Pad')
App.ActiveDocument.Pad.Length = 20.000000
App.ActiveDocument.Pad.Reversed = 0
App.ActiveDocument.Pad.Midplane = 0
App.ActiveDocument.Pad.Length2 = 100.000000
App.ActiveDocument.Pad.Type = 0
App.ActiveDocument.Pad.FaceName = "No face selected"
App.ActiveDocument.recompute()
#Gui.activeDocument().resetEdit()
App.activeDocument().addObject('Sketcher::SketchObject','Sketch001')
#App.activeDocument().Sketch001.Support = (App.ActiveDocument.Pad,["Face8"])
#App.activeDocument().recompute()
#Gui.activeDocument().setEdit('Sketch001')
#App.ActiveDocument.Sketch001.addExternal("Pad","Edge18")
#App.ActiveDocument.recompute()
App.ActiveDocument.Sketch001.addGeometry(Part.Circle(App.Vector(-200.000000,0.000000,0),App.Vector(0,0,1),21.491751))
#App.ActiveDocument.recompute()
App.ActiveDocument.Sketch001.addConstraint(Sketcher.Constraint('Coincident',0,3,-3,3)) 
#App.ActiveDocument.recompute()
App.ActiveDocument.Sketch001.addConstraint(Sketcher.Constraint('Tangent',0, -3)) 
#App.ActiveDocument.recompute()
#App.ActiveDocument.Sketch001.addExternal("Pad","Edge15")
#App.ActiveDocument.recompute()
App.ActiveDocument.Sketch001.addGeometry(Part.Circle(App.Vector(200.000000,0.000000,0),App.Vector(0,0,1),20.605164))
#App.ActiveDocument.recompute()
App.ActiveDocument.Sketch001.addConstraint(Sketcher.Constraint('Coincident',1,3,-4,3)) 
#App.ActiveDocument.recompute()
App.ActiveDocument.Sketch001.addConstraint(Sketcher.Constraint('Tangent',1, -4)) 
#App.ActiveDocument.recompute()
App.ActiveDocument.Sketch001.addConstraint(Sketcher.Constraint('Equal',1,0)) 
#App.ActiveDocument.recompute()
App.ActiveDocument.Sketch001.addConstraint(Sketcher.Constraint('Equal',-3,0)) 
#App.ActiveDocument.recompute()
App.ActiveDocument.Sketch001.delConstraint(1)
App.ActiveDocument.Sketch001.delConstraint(2)
#Gui.getDocument('Unnamed').resetEdit()
App.getDocument('Unnamed').recompute()
#Gui.activeDocument().activeView().viewAxometric()
App.activeDocument().addObject("PartDesign::Pad","Pad001")
App.activeDocument().Pad001.Sketch = App.activeDocument().Sketch001
App.activeDocument().Pad001.Length = 10.0
#App.ActiveDocument.recompute()
#Gui.activeDocument().hide("Sketch001")
#Gui.activeDocument().hide("Pad")
#Gui.activeDocument().setEdit('Pad001')
#Gui.ActiveDocument.Pad001.ShapeColor=Gui.ActiveDocument.Pad.ShapeColor
#Gui.ActiveDocument.Pad001.LineColor=Gui.ActiveDocument.Pad.LineColor
#Gui.ActiveDocument.Pad001.PointColor=Gui.ActiveDocument.Pad.PointColor
App.ActiveDocument.Pad001.Length = 400.000000
App.ActiveDocument.Pad001.Reversed = 0
App.ActiveDocument.Pad001.Midplane = 0
App.ActiveDocument.Pad001.Length2 = 10.000000
App.ActiveDocument.Pad001.Type = 4
App.ActiveDocument.Pad001.FaceName = "No face selected"
App.ActiveDocument.recompute()
#Gui.activeDocument().resetEdit()
FreeCAD.getDocument("Unnamed").getObject("Pad001").Length2 = 1.00
FreeCAD.getDocument("Unnamed").getObject("Pad001").Length2 = 15.00
App.activeDocument().addObject("PartDesign::Chamfer","Chamfer")
App.activeDocument().Chamfer.Base = (App.ActiveDocument.Pad001,["Edge20"])
#Gui.activeDocument().hide("Pad001")
#Gui.activeDocument().setEdit('Chamfer')
#Gui.ActiveDocument.Chamfer.ShapeColor=Gui.ActiveDocument.Pad001.ShapeColor
#Gui.ActiveDocument.Chamfer.LineColor=Gui.ActiveDocument.Pad001.LineColor
#Gui.ActiveDocument.Chamfer.PointColor=Gui.ActiveDocument.Pad001.PointColor
App.ActiveDocument.Chamfer.Size = 5.000000
App.ActiveDocument.recompute()
#Gui.activeDocument().resetEdit()
FreeCAD.getDocument("Unnamed").getObject("Chamfer").Size = 0.00
FreeCAD.getDocument("Unnamed").getObject("Chamfer").Size = 4.00
FreeCAD.getDocument("Unnamed").getObject("Chamfer").Size = 0.00
FreeCAD.getDocument("Unnamed").getObject("Chamfer").Size = 3.00
FreeCAD.getDocument("Unnamed").getObject("Chamfer").Size = 0.00
FreeCAD.getDocument("Unnamed").getObject("Chamfer").Size = 2.00
App.activeDocument().addObject("PartDesign::Chamfer","Chamfer001")
App.activeDocument().Chamfer001.Base = (App.ActiveDocument.Chamfer,["Edge20"])
#Gui.activeDocument().hide("Chamfer")
#Gui.activeDocument().setEdit('Chamfer001')
#Gui.ActiveDocument.Chamfer001.ShapeColor=Gui.ActiveDocument.Chamfer.ShapeColor
#Gui.ActiveDocument.Chamfer001.LineColor=Gui.ActiveDocument.Chamfer.LineColor
#Gui.ActiveDocument.Chamfer001.PointColor=Gui.ActiveDocument.Chamfer.PointColor
App.ActiveDocument.Chamfer001.Size = 2.000000
App.ActiveDocument.recompute()
#Gui.activeDocument().resetEdit()
#Gui.activeDocument().activeView().viewFront()
#Gui.activeDocument().activeView().viewTop()
App.activeDocument().addObject('Sketcher::SketchObject','Sketch002')
#App.activeDocument().Sketch002.Support = (App.ActiveDocument.Chamfer001,["Face16"])
#App.activeDocument().recompute()
#Gui.activeDocument().setEdit('Sketch002')
#Gui.getDocument('Unnamed').resetEdit()
#App.getDocument('Unnamed').recompute()
#App.ActiveDocument.Sketch002.addExternal("Chamfer001","Edge22")
#Gui.activeDocument().activeView().viewAxometric()
#App.ActiveDocument.Sketch002.addExternal("Chamfer001","Edge28")
#App.ActiveDocument.recompute()
#Gui.activeDocument().activeView().viewTop()
App.ActiveDocument.Sketch002.addGeometry(Part.Circle(App.Vector(-201.616272,-1.267572,0),App.Vector(0,0,1),34.333939))
#App.ActiveDocument.recompute()
App.ActiveDocument.Sketch002.addConstraint(Sketcher.Constraint('Coincident',0,3,-3,3)) 
#App.ActiveDocument.recompute()
#Gui.activeDocument().activeView().viewAxometric()
App.ActiveDocument.Sketch002.addExternal("Chamfer001","Edge26")
#App.ActiveDocument.recompute()
#Gui.activeDocument().activeView().viewTop()
App.ActiveDocument.Sketch002.addGeometry(Part.Circle(App.Vector(202.950729,-1.267572,0),App.Vector(0,0,1),47.886044))
#App.ActiveDocument.recompute()
App.ActiveDocument.Sketch002.addConstraint(Sketcher.Constraint('Coincident',1,3,-4,3)) 
#App.ActiveDocument.recompute()
App.ActiveDocument.Sketch002.addConstraint(Sketcher.Constraint('Equal',1,0)) 
#App.ActiveDocument.recompute()
App.ActiveDocument.Sketch002.addConstraint(Sketcher.Constraint('Radius',1,47.886044)) 
App.ActiveDocument.Sketch002.setDatum(3,40.000000)
#Gui.getDocument('Unnamed').resetEdit()
App.getDocument('Unnamed').recompute()
App.activeDocument().addObject("PartDesign::Pad","Pad002")
App.activeDocument().Pad002.Sketch = App.activeDocument().Sketch002
App.activeDocument().Pad002.Length = 10.0
#App.ActiveDocument.recompute()
#Gui.activeDocument().hide("Sketch002")
#Gui.activeDocument().hide("Chamfer001")
#Gui.activeDocument().setEdit('Pad002')
#Gui.ActiveDocument.Pad002.ShapeColor=Gui.ActiveDocument.Chamfer001.ShapeColor
#Gui.ActiveDocument.Pad002.LineColor=Gui.ActiveDocument.Chamfer001.LineColor
#Gui.ActiveDocument.Pad002.PointColor=Gui.ActiveDocument.Chamfer001.PointColor
App.ActiveDocument.Pad002.Length = 200.000000
App.ActiveDocument.Pad002.Reversed = 0
App.ActiveDocument.Pad002.Midplane = 1
App.ActiveDocument.Pad002.Length2 = 100.000000
App.ActiveDocument.Pad002.Type = 0
App.ActiveDocument.Pad002.FaceName = "No face selected"
App.ActiveDocument.recompute()
#Gui.activeDocument().resetEdit()
#Gui.activeDocument().activeView().viewFront()
FreeCAD.getDocument("Unnamed").getObject("Pad001").Length = 0.00
FreeCAD.getDocument("Unnamed").getObject("Pad001").Length = 300.00
FreeCADGui.getDocument("Unnamed").getObject("Pad002").DisplayMode = "Wireframe"
#Gui.activeDocument().activeView().viewAxometric()
FreeCADGui.getDocument("Unnamed").getObject("Pad002").DisplayMode = "Shaded"
FreeCADGui.getDocument("Unnamed").getObject("Pad002").DisplayMode = "Flat Lines"
App.activeDocument().addObject('Sketcher::SketchObject','Sketch003')
#App.activeDocument().Sketch003.Support = (App.ActiveDocument.Pad002,["Face20"])
#App.activeDocument().recompute()
#Gui.activeDocument().setEdit('Sketch003')
#Gui.activeDocument().activeView().viewAxometric()
FreeCADGui.getDocument("Unnamed").getObject("Pad002").DisplayMode = "Wireframe"
App.ActiveDocument.Sketch003.addExternal("Pad002","Edge29")
App.ActiveDocument.Sketch003.addExternal("Pad002","Edge26")
#Gui.activeDocument().activeView().viewTop()
#Gui.activeDocument().activeView().viewAxometric()
App.ActiveDocument.Sketch003.addExternal("Pad002","Edge22")
App.ActiveDocument.Sketch003.addExternal("Pad002","Edge21")
#Gui.activeDocument().activeView().viewTop()
FreeCADGui.getDocument("Unnamed").getObject("Pad002").DisplayMode = "Points"
FreeCADGui.getDocument("Unnamed").getObject("Pad002").DisplayMode = "Points"
FreeCADGui.getDocument("Unnamed").getObject("Pad002").DisplayMode = "Points"
FreeCADGui.getDocument("Unnamed").getObject("Pad002").DisplayMode = "Flat Lines"
FreeCADGui.getDocument("Unnamed").getObject("Pad002").DisplayMode = "Flat Lines"
FreeCADGui.getDocument("Unnamed").getObject("Pad002").DisplayMode = "Flat Lines"
#Gui.activeDocument().activeView().viewAxometric()
App.getDocument("Unnamed").removeObject("Sketch003")
App.ActiveDocument.Sketch002.addGeometry(Part.Line(App.Vector(-168.395050,24.915844,0),App.Vector(173.996414,24.915844,0)))
App.ActiveDocument.Sketch002.addGeometry(Part.Line(App.Vector(173.996414,24.915844,0),App.Vector(173.996414,-30.445967,0)))
App.ActiveDocument.Sketch002.addGeometry(Part.Line(App.Vector(173.996414,-30.445967,0),App.Vector(-168.395050,-30.445967,0)))
App.ActiveDocument.Sketch002.addGeometry(Part.Line(App.Vector(-168.395050,-30.445967,0),App.Vector(-168.395050,24.915844,0)))
App.ActiveDocument.Sketch002.addConstraint(Sketcher.Constraint('Coincident',2,2,3,1)) 
App.ActiveDocument.Sketch002.addConstraint(Sketcher.Constraint('Coincident',3,2,4,1)) 
App.ActiveDocument.Sketch002.addConstraint(Sketcher.Constraint('Coincident',4,2,5,1)) 
App.ActiveDocument.Sketch002.addConstraint(Sketcher.Constraint('Coincident',5,2,2,1)) 
App.ActiveDocument.Sketch002.addConstraint(Sketcher.Constraint('Horizontal',2)) 
App.ActiveDocument.Sketch002.addConstraint(Sketcher.Constraint('Horizontal',4)) 
App.ActiveDocument.Sketch002.addConstraint(Sketcher.Constraint('Vertical',3)) 
App.ActiveDocument.Sketch002.addConstraint(Sketcher.Constraint('Vertical',5)) 
#App.ActiveDocument.recompute()
App.ActiveDocument.Sketch002.addConstraint(Sketcher.Constraint('PointOnObject',2,1,0)) 
#App.ActiveDocument.recompute()
App.ActiveDocument.Sketch002.addConstraint(Sketcher.Constraint('PointOnObject',3,2,1)) 
#App.ActiveDocument.recompute()
App.ActiveDocument.Sketch002.addConstraint(Sketcher.Constraint('PointOnObject',2,1,0)) 
App.ActiveDocument.Sketch002.addConstraint(Sketcher.Constraint('PointOnObject',4,2,0)) 
App.getDocument("Unnamed").removeObject("Pad002")
App.ActiveDocument.Sketch002.addConstraint(Sketcher.Constraint('Symmetric',2,2,2,1,-2)) 
#App.ActiveDocument.recompute()
App.ActiveDocument.Sketch002.delConstraint(14)
App.ActiveDocument.Sketch002.movePoint(2,2,App.Vector(126.302818,2.712082,0),0)
App.ActiveDocument.Sketch002.delConstraint(13)
App.ActiveDocument.Sketch002.addConstraint(Sketcher.Constraint('PointOnObject',2,2,1)) 
#Gui.getDocument('Unnamed').resetEdit()
App.getDocument('Unnamed').recompute()
#Gui.SendMsgToActiveView("SaveAs")
App.getDocument("Unnamed").FileName = "/home/drayko/FreeCAD/fcstd/bug1.fcstd"
App.getDocument("Unnamed").Label = "bug1"
App.getDocument("Unnamed").save()
App.ActiveDocument.Sketch002.delConstraint(15)
App.ActiveDocument.Sketch002.addConstraint(Sketcher.Constraint('DistanceY',3,2,2,2,54.470804)) 
App.ActiveDocument.Sketch002.setDatum(15,50.000000)
#Gui.getDocument('Unnamed').resetEdit()
App.getDocument('Unnamed').recompute()
App.activeDocument().addObject("PartDesign::Pad","Pad002")
App.activeDocument().Pad002.Sketch = App.activeDocument().Sketch002
App.activeDocument().Pad002.Length = 10.0
#App.ActiveDocument.recompute()
#Gui.activeDocument().hide("Sketch002")
#Gui.activeDocument().hide("Chamfer001")
#Gui.activeDocument().setEdit('Pad002')
#Gui.ActiveDocument.Pad002.ShapeColor=Gui.ActiveDocument.Chamfer001.ShapeColor
#Gui.ActiveDocument.Pad002.LineColor=Gui.ActiveDocument.Chamfer001.LineColor
#Gui.ActiveDocument.Pad002.PointColor=Gui.ActiveDocument.Chamfer001.PointColor
App.ActiveDocument.Pad002.Length = 200.000000
App.ActiveDocument.Pad002.Reversed = 0
App.ActiveDocument.Pad002.Midplane = 0
App.ActiveDocument.Pad002.Length2 = 100.000000
App.ActiveDocument.Pad002.Type = 0
App.ActiveDocument.Pad002.FaceName = "No face selected"
App.ActiveDocument.recompute()
#Gui.activeDocument().resetEdit()
#Gui.activeDocument().activeView().viewFront()
#Gui.activeDocument().setEdit('Pad002',0)
App.ActiveDocument.Pad002.Length = 200.000000
App.ActiveDocument.Pad002.Reversed = 0
App.ActiveDocument.Pad002.Midplane = 1
App.ActiveDocument.Pad002.Length2 = 100.000000
App.ActiveDocument.Pad002.Type = 0
App.ActiveDocument.Pad002.FaceName = "No face selected"
App.ActiveDocument.recompute()
#Gui.activeDocument().resetEdit()
App.ActiveDocument.Sketch002.delGeometry(0)
App.ActiveDocument.Sketch002.addGeometry(Part.ArcOfCircle(Part.Circle(App.Vector(-200.000000,0.000000,0),App.Vector(0,0,1),40.000000),-5.608054,-0.675132))
#App.ActiveDocument.recompute()
App.ActiveDocument.Sketch002.addConstraint(Sketcher.Constraint('Coincident',5,3,-3,3)) 
#App.ActiveDocument.recompute()
App.ActiveDocument.Sketch002.addConstraint(Sketcher.Constraint('Coincident',5,2,3,2)) 
#App.ActiveDocument.recompute()
App.ActiveDocument.Sketch002.addConstraint(Sketcher.Constraint('Coincident',5,1,1,1)) 
#App.ActiveDocument.recompute()
App.ActiveDocument.Sketch002.delGeometry(4)
App.getDocument("Unnamed").removeObject("Pad002")
App.ActiveDocument.Sketch002.delGeometry(0)
App.ActiveDocument.Sketch002.addGeometry(Part.ArcOfCircle(Part.Circle(App.Vector(200.000000,0.000000,0),App.Vector(0,0,1),40.000011),-2.466461,2.466461))
#App.ActiveDocument.recompute()
App.ActiveDocument.Sketch002.addConstraint(Sketcher.Constraint('Coincident',4,3,-4,3)) 
#App.ActiveDocument.recompute()
App.ActiveDocument.Sketch002.addConstraint(Sketcher.Constraint('Coincident',4,1,1,2)) 
#App.ActiveDocument.recompute()
App.ActiveDocument.Sketch002.addConstraint(Sketcher.Constraint('Coincident',4,2,0,2)) 
#App.ActiveDocument.recompute()
App.ActiveDocument.Sketch002.delGeometry(1)
App.ActiveDocument.Sketch002.addConstraint(Sketcher.Constraint('Radius',2,40.000004)) 
App.ActiveDocument.Sketch002.addConstraint(Sketcher.Constraint('Equal',2,3)) 
#App.ActiveDocument.recompute()
App.ActiveDocument.Sketch002.delConstraint(0)
App.ActiveDocument.Sketch002.delConstraint(9)
App.ActiveDocument.Sketch002.movePoint(1,2,App.Vector(-164.999832,-26.246401,0),0)
#App.ActiveDocument.recompute()
App.ActiveDocument.Sketch002.movePoint(1,2,App.Vector(-188.302353,-38.251343,0),0)
#App.ActiveDocument.recompute()
App.ActiveDocument.Sketch002.addConstraint(Sketcher.Constraint('Coincident',1,1,3,1)) 
#App.ActiveDocument.recompute()
App.ActiveDocument.Sketch002.addConstraint(Sketcher.Constraint('Symmetric',1,2,0,1,-1)) 
#App.ActiveDocument.recompute()
App.ActiveDocument.Sketch002.delConstraint(10)
App.ActiveDocument.Sketch002.addConstraint(Sketcher.Constraint('Symmetric',1,2,0,1,-1)) 
#App.ActiveDocument.recompute()
#Gui.getDocument('Unnamed').resetEdit()
App.getDocument('Unnamed').recompute()
App.ActiveDocument.Sketch002.delConstraint(10)
App.ActiveDocument.Sketch002.addConstraint(Sketcher.Constraint('Equal',2,3)) 
#App.ActiveDocument.recompute()
App.ActiveDocument.Sketch002.movePoint(1,2,App.Vector(-167.583603,-23.434547,0),0)
#App.ActiveDocument.recompute()
App.ActiveDocument.Sketch002.addConstraint(Sketcher.Constraint('Equal',1,0)) 
#App.ActiveDocument.recompute()
App.ActiveDocument.Sketch002.delConstraint(10)
App.ActiveDocument.Sketch002.movePoint(3,3,App.Vector(212.312088,13.784446,0),0)
#App.ActiveDocument.recompute()
#Gui.getDocument('Unnamed').resetEdit()
App.getDocument('Unnamed').recompute()
App.activeDocument().addObject("PartDesign::Pad","Pad002")
App.activeDocument().Pad002.Sketch = App.activeDocument().Sketch002
App.activeDocument().Pad002.Length = 10.0
#App.ActiveDocument.recompute()
#Gui.activeDocument().hide("Sketch002")
#Gui.activeDocument().hide("Chamfer001")
#Gui.activeDocument().setEdit('Pad002')
#Gui.ActiveDocument.Pad002.ShapeColor=Gui.ActiveDocument.Chamfer001.ShapeColor
#Gui.ActiveDocument.Pad002.LineColor=Gui.ActiveDocument.Chamfer001.LineColor
#Gui.ActiveDocument.Pad002.PointColor=Gui.ActiveDocument.Chamfer001.PointColor
App.ActiveDocument.Pad002.Length = 200.000000
App.ActiveDocument.Pad002.Reversed = 0
App.ActiveDocument.Pad002.Midplane = 1
App.ActiveDocument.Pad002.Length2 = 100.000000
App.ActiveDocument.Pad002.Type = 0
App.ActiveDocument.Pad002.FaceName = "No face selected"
App.ActiveDocument.recompute()
#Gui.activeDocument().resetEdit()
#Gui.activeDocument().activeView().viewFront()
#Gui.activeDocument().activeView().viewTop()
#Gui.activeDocument().activeView().viewFront()
#Gui.activeDocument().activeView().viewFront()
#Gui.activeDocument().activeView().viewBottom()
#Gui.activeDocument().activeView().viewFront()
#Gui.activeDocument().activeView().viewRight()
#Gui.activeDocument().activeView().viewAxometric()
#Gui.activeDocument().activeView().viewFront()
#Gui.SendMsgToActiveView("Save")
App.getDocument("Unnamed").save()
#Gui.activeDocument().activeView().viewAxometric()
#Gui.SendMsgToActiveView("SaveAs")
App.getDocument("Unnamed").FileName = "/home/drayko/FreeCAD/fcstd/Simple_modular_press_brake.fcstd"
App.getDocument("Unnamed").Label = "Simple_modular_press_brake"
App.getDocument("Unnamed").save()
App.activeDocument().addObject('Sketcher::SketchObject','Sketch003')
#App.activeDocument().Sketch003.Support = (App.ActiveDocument.Pad002,["Face15"])
#App.activeDocument().recompute()
#Gui.activeDocument().setEdit('Sketch003')
#Gui.activeDocument().activeView().viewAxometric()
App.ActiveDocument.Sketch003.addExternal("Pad002","Edge32")
#App.ActiveDocument.recompute()
App.ActiveDocument.Sketch003.addExternal("Pad002","Edge33")
#App.ActiveDocument.recompute()
App.ActiveDocument.Sketch003.addGeometry(Part.Line(App.Vector(-168.778778,24.994917,0),App.Vector(168.771240,24.994917,0)))
App.ActiveDocument.Sketch003.addGeometry(Part.Line(App.Vector(168.771240,24.994917,0),App.Vector(168.771240,-25.005083,0)))
App.ActiveDocument.Sketch003.addGeometry(Part.Line(App.Vector(168.771240,-25.005083,0),App.Vector(-168.778778,-25.005083,0)))
App.ActiveDocument.Sketch003.addGeometry(Part.Line(App.Vector(-168.778778,-25.005083,0),App.Vector(-168.778778,24.994917,0)))
App.ActiveDocument.Sketch003.addConstraint(Sketcher.Constraint('Coincident',0,2,1,1)) 
App.ActiveDocument.Sketch003.addConstraint(Sketcher.Constraint('Coincident',1,2,2,1)) 
App.ActiveDocument.Sketch003.addConstraint(Sketcher.Constraint('Coincident',2,2,3,1)) 
App.ActiveDocument.Sketch003.addConstraint(Sketcher.Constraint('Coincident',3,2,0,1)) 
App.ActiveDocument.Sketch003.addConstraint(Sketcher.Constraint('Horizontal',0)) 
App.ActiveDocument.Sketch003.addConstraint(Sketcher.Constraint('Horizontal',2)) 
App.ActiveDocument.Sketch003.addConstraint(Sketcher.Constraint('Vertical',1)) 
App.ActiveDocument.Sketch003.addConstraint(Sketcher.Constraint('Vertical',3)) 
#App.ActiveDocument.recompute()
App.ActiveDocument.Sketch003.addConstraint(Sketcher.Constraint('Coincident',0,1,-3,2)) 
#App.ActiveDocument.recompute()
App.ActiveDocument.Sketch003.addConstraint(Sketcher.Constraint('Coincident',1,2,-4,2)) 
#App.ActiveDocument.recompute()
#Gui.getDocument('Unnamed').resetEdit()
App.getDocument('Unnamed').recompute()
App.activeDocument().addObject("PartDesign::Pad","Pad003")
App.activeDocument().Pad003.Sketch = App.activeDocument().Sketch003
App.activeDocument().Pad003.Length = 10.0
#App.ActiveDocument.recompute()
#Gui.activeDocument().hide("Sketch003")
#Gui.activeDocument().hide("Pad002")
#Gui.activeDocument().setEdit('Pad003')
#Gui.ActiveDocument.Pad003.ShapeColor=Gui.ActiveDocument.Pad002.ShapeColor
#Gui.ActiveDocument.Pad003.LineColor=Gui.ActiveDocument.Pad002.LineColor
#Gui.ActiveDocument.Pad003.PointColor=Gui.ActiveDocument.Pad002.PointColor
App.ActiveDocument.Pad003.Length = 25.000000
App.ActiveDocument.Pad003.Reversed = 0
App.ActiveDocument.Pad003.Midplane = 0
App.ActiveDocument.Pad003.Length2 = 100.000000
App.ActiveDocument.Pad003.Type = 0
App.ActiveDocument.Pad003.FaceName = "No face selected"
App.ActiveDocument.recompute()
#Gui.activeDocument().resetEdit()
App.activeDocument().addObject('Sketcher::SketchObject','Sketch004')
#App.activeDocument().Sketch004.Support = (App.ActiveDocument.Pad003,["Face18"])
#App.activeDocument().recompute()
#Gui.activeDocument().setEdit('Sketch004')
App.ActiveDocument.Sketch004.addExternal("Pad003","Edge40")
#App.ActiveDocument.recompute()
App.ActiveDocument.Sketch004.addExternal("Pad003","Edge38")
#App.ActiveDocument.recompute()
#Gui.activeDocument().activeView().viewRight()
App.ActiveDocument.Sketch004.addGeometry(Part.Line(App.Vector(-25.000000,220.000000,0),App.Vector(25.390165,218.603455,0)))
App.ActiveDocument.Sketch004.addConstraint(Sketcher.Constraint('Coincident',-4,1,0,1)) 
#App.ActiveDocument.recompute()
#App.ActiveDocument.recompute()
App.ActiveDocument.Sketch004.addConstraint(Sketcher.Constraint('Coincident',0,2,-3,1)) 
#App.ActiveDocument.recompute()
App.ActiveDocument.Sketch004.addConstraint(Sketcher.Constraint('Horizontal',0)) 
#App.ActiveDocument.recompute()
App.ActiveDocument.Sketch004.addGeometry(Part.Line(App.Vector(25.000000,220.000000,0),App.Vector(42.984154,192.212509,0)))
App.ActiveDocument.Sketch004.addConstraint(Sketcher.Constraint('Coincident',0,2,1,1)) 
#App.ActiveDocument.recompute()
#App.ActiveDocument.recompute()
App.ActiveDocument.Sketch004.addGeometry(Part.Line(App.Vector(42.984154,192.212509,0),App.Vector(-39.121071,190.746338,0)))
App.ActiveDocument.Sketch004.addConstraint(Sketcher.Constraint('Coincident',1,2,2,1)) 
#App.ActiveDocument.recompute()
#App.ActiveDocument.recompute()
App.ActiveDocument.Sketch004.addConstraint(Sketcher.Constraint('Horizontal',2)) 
#App.ActiveDocument.recompute()
App.ActiveDocument.Sketch004.addGeometry(Part.Line(App.Vector(-39.121071,190.746338,0),App.Vector(-26.658667,219.336533,0)))
App.ActiveDocument.Sketch004.addConstraint(Sketcher.Constraint('Coincident',2,2,3,1)) 
#App.ActiveDocument.recompute()
#App.ActiveDocument.recompute()
App.ActiveDocument.Sketch004.addConstraint(Sketcher.Constraint('Coincident',3,2,0,1)) 
#App.ActiveDocument.recompute()
App.ActiveDocument.Sketch004.addConstraint(Sketcher.Constraint('PointOnObject',-3,2,2)) 
App.ActiveDocument.Sketch004.addConstraint(Sketcher.Constraint('Symmetric',1,2,2,2,-2)) 
#App.ActiveDocument.recompute()
App.ActiveDocument.Sketch004.addConstraint(Sketcher.Constraint('Angle',-3,1,1,1,0.574407)) 
App.ActiveDocument.Sketch004.setDatum(10,0.523599)
App.ActiveDocument.Sketch004.delConstraint(2)
#Gui.getDocument('Unnamed').resetEdit()
App.getDocument('Unnamed').recompute()
#Gui.activeDocument().activeView().viewAxometric()
App.getDocument("Unnamed").removeObject("Sketch004")
App.activeDocument().addObject('Sketcher::SketchObject','Sketch004')
#App.activeDocument().Sketch004.Support = (App.ActiveDocument.Pad003,["Face24"])
#App.activeDocument().recompute()
#Gui.activeDocument().setEdit('Sketch004')
App.ActiveDocument.Sketch004.addGeometry(Part.Point(App.Vector(437.352386,385.350830,0)))
#App.ActiveDocument.recompute()
App.ActiveDocument.Sketch004.delGeometry(0)
App.ActiveDocument.Sketch004.addExternal("Pad003","Edge47")
#App.ActiveDocument.recompute()
App.ActiveDocument.Sketch004.addExternal("Pad003","Edge51")
#App.ActiveDocument.recompute()
App.ActiveDocument.Sketch004.addGeometry(Part.Line(App.Vector(-168.173569,219.674225,0),App.Vector(168.775009,219.674225,0)))
App.ActiveDocument.Sketch004.addGeometry(Part.Line(App.Vector(168.775009,219.674225,0),App.Vector(168.775009,195.000031,0)))
App.ActiveDocument.Sketch004.addGeometry(Part.Line(App.Vector(168.775009,195.000031,0),App.Vector(-168.173569,195.000031,0)))
App.ActiveDocument.Sketch004.addGeometry(Part.Line(App.Vector(-168.173569,195.000031,0),App.Vector(-168.173569,219.674225,0)))
App.ActiveDocument.Sketch004.addConstraint(Sketcher.Constraint('Coincident',0,2,1,1)) 
App.ActiveDocument.Sketch004.addConstraint(Sketcher.Constraint('Coincident',1,2,2,1)) 
App.ActiveDocument.Sketch004.addConstraint(Sketcher.Constraint('Coincident',2,2,3,1)) 
App.ActiveDocument.Sketch004.addConstraint(Sketcher.Constraint('Coincident',3,2,0,1)) 
App.ActiveDocument.Sketch004.addConstraint(Sketcher.Constraint('Horizontal',0)) 
App.ActiveDocument.Sketch004.addConstraint(Sketcher.Constraint('Horizontal',2)) 
App.ActiveDocument.Sketch004.addConstraint(Sketcher.Constraint('Vertical',1)) 
App.ActiveDocument.Sketch004.addConstraint(Sketcher.Constraint('Vertical',3)) 
#App.ActiveDocument.recompute()
App.ActiveDocument.Sketch004.addConstraint(Sketcher.Constraint('Coincident',0,1,-3,2)) 
#App.ActiveDocument.recompute()
App.ActiveDocument.Sketch004.addConstraint(Sketcher.Constraint('Coincident',1,2,-4,2)) 
#App.ActiveDocument.recompute()
#Gui.getDocument('Unnamed').resetEdit()
App.getDocument('Unnamed').recompute()
App.activeDocument().addObject("PartDesign::Pad","Pad004")
App.activeDocument().Pad004.Sketch = App.activeDocument().Sketch004
App.activeDocument().Pad004.Length = 10.0
#App.ActiveDocument.recompute()
#Gui.activeDocument().hide("Sketch004")
#Gui.activeDocument().hide("Pad003")
#Gui.activeDocument().setEdit('Pad004')
#Gui.ActiveDocument.Pad004.ShapeColor=Gui.ActiveDocument.Pad003.ShapeColor
#Gui.ActiveDocument.Pad004.LineColor=Gui.ActiveDocument.Pad003.LineColor
#Gui.ActiveDocument.Pad004.PointColor=Gui.ActiveDocument.Pad003.PointColor
#Gui.activeDocument().activeView().viewRight()
App.ActiveDocument.Pad004.Length = 10.000000
App.ActiveDocument.Pad004.Reversed = 0
App.ActiveDocument.Pad004.Midplane = 0
App.ActiveDocument.Pad004.Length2 = 60.000000
App.ActiveDocument.Pad004.Type = 4
App.ActiveDocument.Pad004.FaceName = "No face selected"
App.ActiveDocument.recompute()
#Gui.activeDocument().resetEdit()
App.activeDocument().addObject('Sketcher::SketchObject','Sketch005')
#App.activeDocument().Sketch005.Support = (App.ActiveDocument.Pad004,["Face24"])
#App.activeDocument().recompute()
#Gui.activeDocument().setEdit('Sketch005')
App.ActiveDocument.Sketch005.addExternal("Pad004","Edge52")
#App.ActiveDocument.recompute()
App.ActiveDocument.Sketch005.addExternal("Pad004","Edge38")
#App.ActiveDocument.recompute()
App.ActiveDocument.Sketch005.addGeometry(Part.Line(App.Vector(-35.000000,195.000000,0),App.Vector(-25.391136,221.140442,0)))
App.ActiveDocument.Sketch005.addConstraint(Sketcher.Constraint('Coincident',-3,2,0,1)) 
#App.ActiveDocument.recompute()
#App.ActiveDocument.recompute()
App.ActiveDocument.Sketch005.addConstraint(Sketcher.Constraint('Coincident',0,2,-4,1)) 
#App.ActiveDocument.recompute()
App.ActiveDocument.Sketch005.addGeometry(Part.Line(App.Vector(-25.000000,220.000000,0),App.Vector(-24.658056,194.749466,0)))
App.ActiveDocument.Sketch005.addConstraint(Sketcher.Constraint('Coincident',0,2,1,1)) 
#App.ActiveDocument.recompute()
#App.ActiveDocument.recompute()
App.ActiveDocument.Sketch005.addConstraint(Sketcher.Constraint('Coincident',1,2,-4,2)) 
#App.ActiveDocument.recompute()
App.ActiveDocument.Sketch005.addConstraint(Sketcher.Constraint('Vertical',1)) 
#App.ActiveDocument.recompute()
App.ActiveDocument.Sketch005.addGeometry(Part.Line(App.Vector(-25.000000,195.000000,0),App.Vector(-34.188145,194.749466,0)))
App.ActiveDocument.Sketch005.addConstraint(Sketcher.Constraint('Coincident',1,2,2,1)) 
#App.ActiveDocument.recompute()
#App.ActiveDocument.recompute()
App.ActiveDocument.Sketch005.addConstraint(Sketcher.Constraint('Horizontal',2)) 
#App.ActiveDocument.recompute()
App.ActiveDocument.Sketch005.addGeometry(Part.Line(App.Vector(25.924589,218.941193,0),App.Vector(36.920807,193.283310,0)))
#App.ActiveDocument.recompute()
App.ActiveDocument.Sketch005.addGeometry(Part.Line(App.Vector(36.920807,193.283310,0),App.Vector(23.725323,194.016388,0)))
App.ActiveDocument.Sketch005.addConstraint(Sketcher.Constraint('Coincident',3,2,4,1)) 
#App.ActiveDocument.recompute()
#App.ActiveDocument.recompute()
App.ActiveDocument.Sketch005.addGeometry(Part.Line(App.Vector(23.725323,194.016388,0),App.Vector(26.657639,218.208084,0)))
App.ActiveDocument.Sketch005.addConstraint(Sketcher.Constraint('Coincident',4,2,5,1)) 
#App.ActiveDocument.recompute()
#App.ActiveDocument.recompute()
App.ActiveDocument.Sketch005.addConstraint(Sketcher.Constraint('Coincident',5,2,3,1)) 
#App.ActiveDocument.recompute()
App.ActiveDocument.Sketch005.addConstraint(Sketcher.Constraint('Symmetric',4,2,1,2,-2)) 
#App.ActiveDocument.recompute()
App.ActiveDocument.Sketch005.addConstraint(Sketcher.Constraint('Symmetric',3,2,2,2,-2)) 
#App.ActiveDocument.recompute()
App.ActiveDocument.Sketch005.addConstraint(Sketcher.Constraint('Symmetric',3,1,0,2,-2)) 
#App.ActiveDocument.recompute()
App.ActiveDocument.Sketch005.delConstraint(4)
App.ActiveDocument.Sketch005.movePoint(3,2,App.Vector(55.247932,191.084061,0),0)
#App.ActiveDocument.recompute()
App.ActiveDocument.Sketch005.delConstraintOnPoint(7)
App.ActiveDocument.Sketch005.delConstraintOnPoint(5)
App.ActiveDocument.Sketch005.delConstraintOnPoint(5)
App.ActiveDocument.Sketch005.delGeometry(2)
App.ActiveDocument.Sketch005.addGeometry(Part.Line(App.Vector(-25.000000,195.000000,0),App.Vector(-35.000000,195.000000,0)))
#App.ActiveDocument.recompute()
App.ActiveDocument.Sketch005.addConstraint(Sketcher.Constraint('Coincident',5,1,1,2)) 
#App.ActiveDocument.recompute()
App.ActiveDocument.Sketch005.addConstraint(Sketcher.Constraint('Coincident',5,2,0,1)) 
#App.ActiveDocument.recompute()
App.ActiveDocument.Sketch005.addConstraint(Sketcher.Constraint('Horizontal',5)) 
#App.ActiveDocument.recompute()
App.ActiveDocument.Sketch005.addConstraint(Sketcher.Constraint('Symmetric',2,2,0,1,-2)) 
#App.ActiveDocument.recompute()
App.ActiveDocument.Sketch005.addConstraint(Sketcher.Constraint('Coincident',3,1,2,2)) 
#App.ActiveDocument.recompute()
App.ActiveDocument.Sketch005.delConstraint(10)
#Gui.getDocument('Unnamed').resetEdit()
App.getDocument('Unnamed').recompute()
App.activeDocument().addObject("PartDesign::Pocket","Pocket")
App.activeDocument().Pocket.Sketch = App.activeDocument().Sketch005
App.activeDocument().Pocket.Length = 5.0
#App.ActiveDocument.recompute()
#Gui.activeDocument().hide("Sketch005")
#Gui.activeDocument().hide("Pad004")
#Gui.activeDocument().setEdit('Pocket')
#Gui.ActiveDocument.Pocket.ShapeColor=Gui.ActiveDocument.Pad004.ShapeColor
#Gui.ActiveDocument.Pocket.LineColor=Gui.ActiveDocument.Pad004.LineColor
#Gui.ActiveDocument.Pocket.PointColor=Gui.ActiveDocument.Pad004.PointColor
App.ActiveDocument.Pocket.Length = 5.000000
App.ActiveDocument.Pocket.Type = 4
App.ActiveDocument.Pocket.FaceName = ""
App.ActiveDocument.recompute()
#Gui.activeDocument().resetEdit()
FreeCAD.getDocument("Unnamed").getObject("Pocket").Type = "UpToLast"
FreeCAD.getDocument("Unnamed").getObject("Pocket").Type = "ThroughAll"
#Gui.activeDocument().setEdit('Pocket',0)
App.ActiveDocument.Pocket.Length = 5.000000
App.ActiveDocument.Pocket.Type = 4
App.ActiveDocument.Pocket.FaceName = "Face19"
App.ActiveDocument.recompute()
#Gui.activeDocument().resetEdit()
#Gui.activeDocument().setEdit('Pocket',0)
#Gui.activeDocument().resetEdit()
App.getDocument("Unnamed").removeObject("Pocket")
App.ActiveDocument.Sketch005.delConstraintOnPoint(7)
App.ActiveDocument.Sketch005.delGeometry(4)
App.ActiveDocument.Sketch005.delGeometry(3)
App.ActiveDocument.Sketch005.delGeometry(1)
App.ActiveDocument.Sketch005.delConstraintOnPoint(4)
App.ActiveDocument.Sketch005.delGeometry(2)
App.ActiveDocument.Sketch005.delExternal(1)
App.ActiveDocument.Sketch005.addGeometry(Part.Line(App.Vector(-35.000000,195.000000,0),App.Vector(-35.330559,219.416031,0)))
App.ActiveDocument.Sketch005.addConstraint(Sketcher.Constraint('Coincident',0,1,2,1)) 
#App.ActiveDocument.recompute()
#App.ActiveDocument.recompute()
App.ActiveDocument.Sketch005.addConstraint(Sketcher.Constraint('Coincident',2,2,-3,1)) 
#App.ActiveDocument.recompute()
App.ActiveDocument.Sketch005.addConstraint(Sketcher.Constraint('Vertical',2)) 
#App.ActiveDocument.recompute()
App.ActiveDocument.Sketch005.addGeometry(Part.Line(App.Vector(-35.000000,220.000000,0),App.Vector(-25.141348,219.416031,0)))
App.ActiveDocument.Sketch005.addConstraint(Sketcher.Constraint('Coincident',2,2,3,1)) 
#App.ActiveDocument.recompute()
#App.ActiveDocument.recompute()
App.ActiveDocument.Sketch005.addConstraint(Sketcher.Constraint('Coincident',3,2,0,2)) 
#App.ActiveDocument.recompute()
App.ActiveDocument.Sketch005.addGeometry(Part.Line(App.Vector(35.000000,195.000000,0),App.Vector(34.595367,219.216232,0)))
App.ActiveDocument.Sketch005.addConstraint(Sketcher.Constraint('Coincident',1,2,4,1)) 
#App.ActiveDocument.recompute()
#App.ActiveDocument.recompute()
App.ActiveDocument.Sketch005.addConstraint(Sketcher.Constraint('Vertical',4)) 
#App.ActiveDocument.recompute()
App.ActiveDocument.Sketch005.addGeometry(Part.Line(App.Vector(34.595367,219.216232,0),App.Vector(24.805746,219.416031,0)))
App.ActiveDocument.Sketch005.addConstraint(Sketcher.Constraint('Coincident',4,2,5,1)) 
#App.ActiveDocument.recompute()
#App.ActiveDocument.recompute()
App.ActiveDocument.Sketch005.addConstraint(Sketcher.Constraint('Coincident',5,2,1,1)) 
#App.ActiveDocument.recompute()
App.ActiveDocument.Sketch005.addConstraint(Sketcher.Constraint('Horizontal',5)) 
#App.ActiveDocument.recompute()
App.ActiveDocument.Sketch005.addConstraint(Sketcher.Constraint('Symmetric',4,2,2,2,-2)) 
#App.ActiveDocument.recompute()
App.ActiveDocument.Sketch005.movePoint(2,0,App.Vector(-6.482326,-3.626987,0),1)
#App.ActiveDocument.recompute()
App.ActiveDocument.Sketch005.movePoint(4,0,App.Vector(12.188688,4.568454,0),1)
#App.ActiveDocument.recompute()
App.ActiveDocument.Sketch005.delConstraint(9)
App.ActiveDocument.Sketch005.delConstraint(5)
App.ActiveDocument.Sketch005.delConstraint(10)
App.ActiveDocument.Sketch005.movePoint(2,0,App.Vector(8.816027,0.363804,0),1)
#App.ActiveDocument.recompute()
App.ActiveDocument.Sketch005.movePoint(0,0,App.Vector(-4.849441,-8.209353,0),1)
#App.ActiveDocument.recompute()
App.ActiveDocument.Sketch005.addExternal("Pad004","Edge38")
#App.ActiveDocument.recompute()
App.ActiveDocument.Sketch005.addConstraint(Sketcher.Constraint('Coincident',0,2,-4,1)) 
#App.ActiveDocument.recompute()
App.ActiveDocument.Sketch005.delConstraintOnPoint(13)
App.ActiveDocument.Sketch005.movePoint(-4,2,App.Vector(-34.073471,186.288040,0),0)
#App.ActiveDocument.recompute()
#Gui.getDocument('Unnamed').resetEdit()
App.getDocument('Unnamed').recompute()
App.ActiveDocument.Sketch005.delConstraintOnPoint(13)
#Gui.getDocument('Unnamed').resetEdit()
App.getDocument('Unnamed').recompute()
App.activeDocument().addObject("PartDesign::Pocket","Pocket")
App.activeDocument().Pocket.Sketch = App.activeDocument().Sketch005
App.activeDocument().Pocket.Length = 5.0
#App.ActiveDocument.recompute()
#Gui.activeDocument().hide("Sketch005")
#Gui.activeDocument().hide("Pad004")
#Gui.activeDocument().setEdit('Pocket')
#Gui.ActiveDocument.Pocket.ShapeColor=Gui.ActiveDocument.Pad004.ShapeColor
#Gui.ActiveDocument.Pocket.LineColor=Gui.ActiveDocument.Pad004.LineColor
#Gui.ActiveDocument.Pocket.PointColor=Gui.ActiveDocument.Pad004.PointColor
App.ActiveDocument.Pocket.Length = 50.000000
App.ActiveDocument.Pocket.Type = 0
App.ActiveDocument.Pocket.FaceName = ""
App.ActiveDocument.recompute()
#Gui.activeDocument().resetEdit()
#Gui.activeDocument().setEdit('Pocket',0)
App.ActiveDocument.Pocket.Length = 50.000000
App.ActiveDocument.Pocket.Type = 4
App.ActiveDocument.Pocket.FaceName = "Face21"
App.ActiveDocument.recompute()
#Gui.activeDocument().resetEdit()
#Gui.activeDocument().setEdit('Pocket',0)
#Gui.activeDocument().activeView().viewAxometric()
#Gui.activeDocument().activeView().viewAxometric()
App.ActiveDocument.Pocket.Length = 50.000000
App.ActiveDocument.Pocket.Type = 3
App.ActiveDocument.Pocket.FaceName = "Face21"
App.ActiveDocument.recompute()
#Gui.activeDocument().resetEdit()
#Gui.SendMsgToActiveView("Save")
App.getDocument("Unnamed").save()
FreeCADGui.getDocument("Unnamed").getObject("Pocket").Visibility = False
FreeCADGui.getDocument("Unnamed").getObject("Pad003").Visibility = True
FreeCADGui.getDocument("Unnamed").getObject("Pad003").Visibility = False
FreeCADGui.getDocument("Unnamed").getObject("Pad002").Visibility = True
FreeCADGui.getDocument("Unnamed").getObject("Pad002").Visibility = False
#Gui.activeDocument().setEdit('Pad003',0)
App.ActiveDocument.Pad003.Length = 25.000000
App.ActiveDocument.Pad003.Reversed = 0
App.ActiveDocument.Pad003.Midplane = 0
App.ActiveDocument.Pad003.Length2 = 100.000000
App.ActiveDocument.Pad003.Type = 0
App.ActiveDocument.Pad003.FaceName = "No face selected"
App.ActiveDocument.recompute()
#Gui.activeDocument().resetEdit()
FreeCADGui.getDocument("Unnamed").getObject("Pad003").Visibility = True
App.activeDocument().addObject('Sketcher::SketchObject','Sketch006')
#App.activeDocument().Sketch006.Support = (App.ActiveDocument.Pad003,["Face18"])
#App.activeDocument().recompute()
#Gui.activeDocument().setEdit('Sketch006')
App.ActiveDocument.Sketch006.addExternal("Pad003","Edge39")
#App.ActiveDocument.recompute()
#Gui.activeDocument().activeView().viewFront()
#Gui.activeDocument().activeView().viewRight()
App.ActiveDocument.Sketch006.addGeometry(Part.Line(App.Vector(-25.000000,195.000000,0),App.Vector(26.450525,193.006287,0)))
App.ActiveDocument.Sketch006.addConstraint(Sketcher.Constraint('Coincident',-3,1,0,1)) 
#App.ActiveDocument.recompute()
#App.ActiveDocument.recompute()
App.ActiveDocument.Sketch006.addConstraint(Sketcher.Constraint('Coincident',0,2,-3,2)) 
#App.ActiveDocument.recompute()
App.ActiveDocument.Sketch006.addGeometry(Part.Line(App.Vector(25.000000,195.000000,0),App.Vector(0.049654,158.433701,0)))
App.ActiveDocument.Sketch006.addConstraint(Sketcher.Constraint('Coincident',0,2,1,1)) 
#App.ActiveDocument.recompute()
#App.ActiveDocument.recompute()
App.ActiveDocument.Sketch006.addGeometry(Part.Line(App.Vector(0.049654,158.433701,0),App.Vector(-25.094038,194.263474,0)))
App.ActiveDocument.Sketch006.addConstraint(Sketcher.Constraint('Coincident',1,2,2,1)) 
#App.ActiveDocument.recompute()
#App.ActiveDocument.recompute()
App.ActiveDocument.Sketch006.addConstraint(Sketcher.Constraint('Coincident',2,2,0,1)) 
#App.ActiveDocument.recompute()
App.ActiveDocument.Sketch006.addConstraint(Sketcher.Constraint('Angle',1,2,2,1,1.199390)) 
App.ActiveDocument.Sketch006.setDatum(5,1.047198)
#Gui.activeDocument().activeView().viewAxometric()
App.ActiveDocument.Sketch006.movePoint(1,2,App.Vector(-13.477835,157.912300,0),0)
#App.ActiveDocument.recompute()
App.ActiveDocument.Sketch006.addConstraint(Sketcher.Constraint('PointOnObject',1,2,-2)) 
#Gui.getDocument('Unnamed').resetEdit()
App.getDocument('Unnamed').recompute()
App.activeDocument().addObject("PartDesign::Pad","Pad005")
App.activeDocument().Pad005.Sketch = App.activeDocument().Sketch006
App.activeDocument().Pad005.Length = 10.0
#App.ActiveDocument.recompute()
#Gui.activeDocument().hide("Sketch006")
#Gui.activeDocument().hide("Pad003")
#Gui.activeDocument().setEdit('Pad005')
#Gui.ActiveDocument.Pad005.ShapeColor=Gui.ActiveDocument.Pad003.ShapeColor
#Gui.ActiveDocument.Pad005.LineColor=Gui.ActiveDocument.Pad003.LineColor
#Gui.ActiveDocument.Pad005.PointColor=Gui.ActiveDocument.Pad003.PointColor
App.ActiveDocument.Pad005.Length = 100.000000
App.ActiveDocument.Pad005.Reversed = 0
App.ActiveDocument.Pad005.Midplane = 0
App.ActiveDocument.Pad005.Length2 = 100.000000
App.ActiveDocument.Pad005.Type = 0
App.ActiveDocument.Pad005.FaceName = "No face selected"
App.ActiveDocument.recompute()
#Gui.activeDocument().resetEdit()
#Gui.activeDocument().setEdit('Pad005',0)
#Gui.activeDocument().activeView().viewLeft()
#Gui.activeDocument().activeView().viewAxometric()
App.ActiveDocument.Pad005.Length = 100.000000
App.ActiveDocument.Pad005.Reversed = 1
App.ActiveDocument.Pad005.Midplane = 0
App.ActiveDocument.Pad005.Length2 = 100.000000
App.ActiveDocument.Pad005.Type = 3
App.ActiveDocument.Pad005.FaceName = "Face21"
App.ActiveDocument.recompute()
#Gui.activeDocument().resetEdit()
#Gui.activeDocument().setEdit('Pad005',0)
#Gui.activeDocument().activeView().viewFront()
App.ActiveDocument.Pad005.Length = 330.000000
App.ActiveDocument.Pad005.Reversed = 1
App.ActiveDocument.Pad005.Midplane = 0
App.ActiveDocument.Pad005.Length2 = 100.000000
App.ActiveDocument.Pad005.Type = 0
App.ActiveDocument.Pad005.FaceName = "Face21"
App.ActiveDocument.recompute()
#Gui.activeDocument().resetEdit()
#Gui.activateWorkbench("NoneWorkbench")
#Gui.activateWorkbench("PartDesignWorkbench")
#Gui.SendMsgToActiveView("Save")
App.getDocument("Unnamed").save()
#Gui.activateWorkbench("DrawingWorkbench")
App.activeDocument().addObject('Drawing::FeaturePage','Page')
App.activeDocument().Page.Template = '/usr/share/freecad/Mod/Drawing/Templates/A4_Landscape.svg'
App.activeDocument().addObject('Drawing::FeatureViewPart','Ortho')
App.activeDocument().Ortho.Source = App.activeDocument().Pad005
App.activeDocument().Page.addObject(App.activeDocument().Ortho)
App.activeDocument().Ortho.Direction = (1,0,0)
Gui.ActiveDocument.getObject('Ortho').Visibility = False
App.activeDocument().Ortho.X = -10000
App.activeDocument().Ortho.Y = -10000
App.activeDocument().addObject('Drawing::FeatureViewPart','Ortho001')
App.activeDocument().Ortho001.Source = App.activeDocument().Pad005
App.activeDocument().Page.addObject(App.activeDocument().Ortho001)
App.activeDocument().Ortho001.Direction = (1,0,0)
Gui.ActiveDocument.getObject('Ortho001').Visibility = False
App.activeDocument().Ortho001.X = -10000
App.activeDocument().Ortho001.Y = -10000
App.activeDocument().addObject('Drawing::FeatureViewPart','Ortho002')
App.activeDocument().Ortho002.Source = App.activeDocument().Pad005
App.activeDocument().Page.addObject(App.activeDocument().Ortho002)
App.activeDocument().Ortho002.Direction = (1,0,0)
Gui.ActiveDocument.getObject('Ortho002').Visibility = False
App.activeDocument().Ortho002.X = -10000
App.activeDocument().Ortho002.Y = -10000
App.activeDocument().addObject('Drawing::FeatureViewPart','Ortho003')
App.activeDocument().Ortho003.Source = App.activeDocument().Pad005
App.activeDocument().Page.addObject(App.activeDocument().Ortho003)
App.activeDocument().Ortho003.Direction = (1,0,0)
Gui.ActiveDocument.getObject('Ortho003').Visibility = False
App.activeDocument().Ortho003.X = -10000
App.activeDocument().Ortho003.Y = -10000
#App.ActiveDocument.recompute()
Gui.ActiveDocument.getObject('Ortho').Visibility = True
App.activeDocument().Ortho.Direction = (0,1,0)
App.activeDocument().Ortho.Label = 'Front'
App.activeDocument().Ortho.Rotation = -90
App.activeDocument().Ortho.Scale = 0.375000
App.activeDocument().Ortho.X = 148.500000
App.activeDocument().Ortho.Y = 183.750000
#App.ActiveDocument.recompute()
App.activeDocument().Ortho.Direction = (-1,0,0)
App.activeDocument().Ortho.Label = 'Left'
App.activeDocument().Ortho.Rotation = 90
Gui.ActiveDocument.getObject('Ortho').Visibility = True
App.activeDocument().Ortho.Scale = 0.375000
App.activeDocument().Ortho.X = 148.500000
App.activeDocument().Ortho.Y = 183.750000
#App.ActiveDocument.recompute()
App.activeDocument().Ortho.Direction = (0,1,0)
App.activeDocument().Ortho.Label = 'Front'
App.activeDocument().Ortho.Rotation = -90
Gui.ActiveDocument.getObject('Ortho').Visibility = True
App.activeDocument().Ortho.Scale = 0.375000
App.activeDocument().Ortho.X = 148.500000
App.activeDocument().Ortho.Y = 183.750000
#App.ActiveDocument.recompute()
Gui.ActiveDocument.getObject('Ortho001').Visibility = True
App.activeDocument().Ortho001.Direction = (-1,0,0)
App.activeDocument().Ortho001.Label = 'Left'
App.activeDocument().Ortho001.Rotation = 90
App.activeDocument().Ortho.Scale = 0.250000
App.activeDocument().Ortho.X = 106.500000
App.activeDocument().Ortho.Y = 157.500000
App.activeDocument().Ortho001.Scale = 0.250000
App.activeDocument().Ortho001.X = 228.000000
App.activeDocument().Ortho001.Y = 157.500000
#App.ActiveDocument.recompute()
Gui.ActiveDocument.getObject('Ortho002').Visibility = True
App.activeDocument().Ortho002.Direction = (0,0,1)
App.activeDocument().Ortho002.Label = 'Top'
App.activeDocument().Ortho002.Rotation = 0
App.activeDocument().Ortho.Scale = 0.200000
App.activeDocument().Ortho.X = 117.500000
App.activeDocument().Ortho.Y = 116.000000
App.activeDocument().Ortho001.Scale = 0.200000
App.activeDocument().Ortho001.X = 209.500000
App.activeDocument().Ortho001.Y = 116.000000
App.activeDocument().Ortho002.Scale = 0.200000
App.activeDocument().Ortho002.X = 117.500000
App.activeDocument().Ortho002.Y = 158.000000
#App.ActiveDocument.recompute()
App.activeDocument().Ortho.ShowHiddenLines = True
App.activeDocument().Ortho001.ShowHiddenLines = True
App.activeDocument().Ortho002.ShowHiddenLines = True
App.activeDocument().Ortho003.ShowHiddenLines = True
#App.ActiveDocument.recompute()
Gui.ActiveDocument.getObject('Ortho003').Visibility = True
App.activeDocument().Ortho003.Direction = (0,0,-1)
App.activeDocument().Ortho003.Label = 'Bottom'
App.activeDocument().Ortho003.Rotation = 180
App.activeDocument().Ortho.Scale = 0.125000
App.activeDocument().Ortho.X = 125.099998
App.activeDocument().Ortho.Y = 131.250000
App.activeDocument().Ortho001.Scale = 0.125000
App.activeDocument().Ortho001.X = 190.699997
App.activeDocument().Ortho001.Y = 131.250000
App.activeDocument().Ortho002.Scale = 0.125000
App.activeDocument().Ortho002.X = 125.099998
App.activeDocument().Ortho002.Y = 165.600006
App.activeDocument().Ortho003.Scale = 0.125000
App.activeDocument().Ortho003.X = 125.099998
App.activeDocument().Ortho003.Y = 44.400002
#App.ActiveDocument.recompute()
App.activeDocument().Ortho.ShowHiddenLines = False
App.activeDocument().Ortho001.ShowHiddenLines = False
App.activeDocument().Ortho002.ShowHiddenLines = False
App.activeDocument().Ortho003.ShowHiddenLines = False
#App.ActiveDocument.recompute()
App.activeDocument().Ortho.ShowSmoothLines = True
App.activeDocument().Ortho001.ShowSmoothLines = True
App.activeDocument().Ortho002.ShowSmoothLines = True
App.activeDocument().Ortho003.ShowSmoothLines = True
#App.ActiveDocument.recompute()
App.activeDocument().Ortho.ShowHiddenLines = True
App.activeDocument().Ortho001.ShowHiddenLines = True
App.activeDocument().Ortho002.ShowHiddenLines = True
App.activeDocument().Ortho003.ShowHiddenLines = True
#App.ActiveDocument.recompute()
App.activeDocument().Ortho.ShowSmoothLines = False
App.activeDocument().Ortho001.ShowSmoothLines = False
App.activeDocument().Ortho002.ShowSmoothLines = False
App.activeDocument().Ortho003.ShowSmoothLines = False
#App.ActiveDocument.recompute()
Gui.ActiveDocument.getObject('Ortho003').Visibility = False
App.activeDocument().Ortho003.X = -10000
App.activeDocument().Ortho003.Y = -10000
App.activeDocument().Ortho.Scale = 0.200000
App.activeDocument().Ortho.X = 117.500000
App.activeDocument().Ortho.Y = 116.000000
App.activeDocument().Ortho001.Scale = 0.200000
App.activeDocument().Ortho001.X = 209.500000
App.activeDocument().Ortho001.Y = 116.000000
App.activeDocument().Ortho002.Scale = 0.200000
App.activeDocument().Ortho002.X = 117.500000
App.activeDocument().Ortho002.Y = 158.000000
#App.ActiveDocument.recompute()
#1
App.activeDocument().Ortho.Scale = 0.200000
App.activeDocument().Ortho.X = 100.000000
App.activeDocument().Ortho.Y = 116.000000
App.activeDocument().Ortho001.Scale = 0.200000
App.activeDocument().Ortho001.X = 192.000000
App.activeDocument().Ortho001.Y = 116.000000
App.activeDocument().Ortho002.Scale = 0.200000
App.activeDocument().Ortho002.X = 100.000000
App.activeDocument().Ortho002.Y = 158.000000
#App.ActiveDocument.recompute()
#2
#1
App.activeDocument().Ortho.Scale = 0.200000
App.activeDocument().Ortho.X = 90.000000
App.activeDocument().Ortho.Y = 116.000000
App.activeDocument().Ortho001.Scale = 0.200000
App.activeDocument().Ortho001.X = 182.000000
App.activeDocument().Ortho001.Y = 116.000000
App.activeDocument().Ortho002.Scale = 0.200000
App.activeDocument().Ortho002.X = 90.000000
App.activeDocument().Ortho002.Y = 158.000000
#App.ActiveDocument.recompute()
#2
#1
App.activeDocument().Ortho.Scale = 0.200000
App.activeDocument().Ortho.X = 80.000000
App.activeDocument().Ortho.Y = 116.000000
App.activeDocument().Ortho001.Scale = 0.200000
App.activeDocument().Ortho001.X = 172.000000
App.activeDocument().Ortho001.Y = 116.000000
App.activeDocument().Ortho002.Scale = 0.200000
App.activeDocument().Ortho002.X = 80.000000
App.activeDocument().Ortho002.Y = 158.000000
#App.ActiveDocument.recompute()
#2
#1
App.activeDocument().Ortho.Scale = 0.200000
App.activeDocument().Ortho.X = 80.000000
App.activeDocument().Ortho.Y = 116.000000
App.activeDocument().Ortho001.Scale = 0.200000
App.activeDocument().Ortho001.X = 172.000000
App.activeDocument().Ortho001.Y = 116.000000
App.activeDocument().Ortho002.Scale = 0.200000
App.activeDocument().Ortho002.X = 80.000000
App.activeDocument().Ortho002.Y = 158.000000
#App.ActiveDocument.recompute()
#2
App.activeDocument().removeObject('Ortho003')
FreeCAD.getDocument("Unnamed").getObject("Page").EditableTexts = [unicode('Elmo Mntynen', 'utf-8'),]
FreeCAD.getDocument("Unnamed").getObject("Page").EditableTexts = [unicode('', 'utf-8'),]

# Macro End: /home/drayko/FreeCAD/fcstd/Press_brake.FCMacro +++++++++++++++++++++++++++++++++++++++++++++++++
